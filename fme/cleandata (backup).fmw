FME workspace cleandata (backup).fmw

Parameters:
- DestDataset_GEOJSON = $(FME_MF_DIR)gestel.json   # Destination GeoJSON File
- SourceDataset_OSM_3 = $(FME_MF_DIR)data\gestel.osm   # Source OpenStreetMap File(s)
- SourceDataset_GEOJSON = $(FME_MF_DIR)data\gestel-cutout3.geojson   # Source GeoJSON File or URL

Readers:
- OSM_2: OSM from $(SourceDataset_OSM_3)
- GEOJSON_2: GEOJSON from $(SourceDataset_GEOJSON)

Writers:
- GEOJSON_1: GEOJSON to $(DestDataset_GEOJSON)

highway (reader OSM_2)
    attributes: created_by xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, maxspeed xml_buffer, service xml_buffer, proposed xml_buffer, crossing xml_buffer, construction xml_buffer, sport xml_buffer, bicycle xml_buffer, foot xml_buffer, level xml_buffer, wheelchair xml_buffer, distance xml_buffer, surface xml_buffer, public_transport xml_buffer, bus xml_buffer, lanes xml_buffer, tiger:cfcc xml_buffer, area xml_buffer, ref xml_buffer, incline xml_buffer,
      direction xml_buffer, tracktype xml_buffer, oneway xml_buffer, source xml_buffer, highway xml_buffer
    -> IdentifyRoads
IdentifyRoads: TestFilter
    DEFAULT_VALUE = Inaccessible
    PASSED_TEST_GROUP_OUTPUT = FIRST
    TEST_LIST:
      "BOOL_OP,COMPOSITE,COMPOSITE_TEST,""""""1 OR 2 OR 3 OR ( 4 AND 5 AND 6 )"""""",TEST_CLAUSE,TEST @Value(highway) = cycleway
      TEST @Value(highway) = residential
      TEST @Value(highway) = unclassified
      TEST @Value(highway) = tertiary
      TEST @Value(bicycle) != use_sidepath
      TEST @Value(bicycle) != no",Cyclable,"BOOL_OP,OR,COMPOSITE_TEST,""""""1 OR 2 OR 3 OR 4"""""",TEST_CLAUSE,TEST @Value(highway) = footway
      TEST @Value(highway) = track
      TEST @Value(highway) = path
      TEST @Value(highway) = pedestrian",Walkable
    Cyclable -> Cyclable
    Walkable -> Walkable
Cyclable: AttributeCreator
    ATTR_TABLE = SET_TO wandrer_accessibility = cyclable
    -> Intersector
Walkable: AttributeCreator
    ATTR_TABLE = SET_TO wandrer_accessibility = walkable
    -> Intersector
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Clipper [CANDIDATE]
    NODE -> Clipper [CANDIDATE]
gestel-cutout3 (reader GEOJSON_2)
    -> Clipper [CLIPPER]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> SplitClipped
    OUTSIDE -> No
SplitClipped: TestFilter
    DEFAULT_VALUE = Clipped
    PASSED_TEST_GROUP_OUTPUT = FIRST
    TEST_LIST = "BOOL_OP,OR,COMPOSITE_TEST,""""""1"""""",TEST_CLAUSE,TEST @Value(_clipped) = no",Unclipped
    Unclipped -> Yes
    Clipped -> Partial
Yes: AttributeCreator
    ATTR_TABLE = SET_TO wandrer_in_target_area = yes
    -> highway (writer GEOJSON_1)
Partial: AttributeCreator
    ATTR_TABLE = SET_TO wandrer_in_target_area = partial
    -> highway (writer GEOJSON_1)
No: AttributeCreator
    ATTR_TABLE = SET_TO wandrer_in_target_area = no
    -> highway (writer GEOJSON_1)

Bookmark: Writer Feature Types
highway (writer GEOJSON_1)
    attributes: id string, name string, highway string, wandrer_accessibility int, wandrer_in_target_area int
